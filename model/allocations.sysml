// Allocations & traces
package allocations {
    // Allocation examples (illustrative comments)
    // allocation requirements::SystemComfortRangeReq -> functional::ControlLoop;
    // allocation functional::OptimizeEnergy -> logical::EnergyOptimizer;
    // allocation functional::PredictMaintenance -> logical::AnalyticsService;

    // Trace placeholders
    // satisfy requirements::SystemEnergyReductionReq by logical::EnergyOptimizer;
    // verify requirements::SystemCO2LimitReq by verification::CO2VentilationTest;
}
